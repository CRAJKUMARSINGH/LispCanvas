(DEFUN C:Rplan()
(SETQ X (FIX 0))
(SETQ NOFLINES (GETINT "GIVE VALUE OF NUMBER OF LINES;"))
(SETQ PT1(LIST 10 10))

(REPEAT NOFLINES
        (SETQ X(+ X 1))
		(SETQ LENGTH(GETREAL "GIVE VALUE OF LENGTH OF NEXT LINE IN M;"))
		(SETQ ANGLE(GETREAL "GIVE VALUE OF ANGLE OF NEXT LINE IN DEGREES;"))
        	(SETQ RANGLE(* ANGLE 0.01746))

(SETQ COSTHETA(COS RANGLE))
(SETQ SINTHETA(SIN RANGLE))

(SETQ H(* LENGTH COSTHETA))
(SETQ V(* LENGTH SINTHETA))

(SETQ PT2(LIST(+ H (NTH 0 PT1))(+ V (NTH 1 PT1))))
		(COMMAND "LINE" PT1 PT2 *CANCEL*)
(SETQ PT1(LIST(NTH 0 PT2) (NTH 1 PT2)))        
                 )

(COMMAND "ZOOM" "EXTENTS" "ZOOM" "VMAX")

   )
