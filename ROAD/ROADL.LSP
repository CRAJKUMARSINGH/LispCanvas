(DEFUN C:ROADL()
(SETQ LENGTH(GETREAL "GIVE VALUE OF LENGTH OF ROAD IN M;"))
(SETQ INTERVAL(GETREAL "GIVE INTERVAL OF SURVEY OF ROAD CROSS SECTION IN M;"))
(SETQ MAXLEVEL(GETREAL "GIVE MAXIMUM LEVEL IN M;"))
(SETQ MINLEVEL(GETREAL "GIVE MINIMUM LEVEL IN M;"))
(SETQ NSL(GETREAL "GIVE NSL OF FIRST POINT IN M;"))
(SETQ NOFPOINT(FIX(+ 0 (/ LENGTH INTERVAL))))
(SETQ DAT1(FIX MINLEVEL ))
(SETQ DAT2(FIX (/ MINLEVEL 10)))
(SETQ DAT3(FIX (- DAT1 (* 10 DAT2))))
(SETQ DAT4(FIX (/ DAT3 5)))
(SETQ DATUM(FIX (+ (* DAT2 10) (* 5 DAT4))))
(SETQ X (FIX 0))
(SETQ CY (- NSL DATUM))
(SETQ PTX(LIST 0 CY))

        (SETQ PTVERTICAL1(LIST 0 -8))
        (SETQ PTVERTICAL2(LIST 0 (- MAXLEVEL DATUM)))
        (COMMAND "LINE" PTVERTICAL1 PTVERTICAL2 *CANCEL*)

(SETQ CXDATUM1 (* 30 -0.45))
        (SETQ CYDATUM1 (FLOAT 0))
        (SETQ PTDATUM1(LIST CXDATUM1 CYDATUM1))
        (SETQ CXDATUM2 (/ LENGTH 10))
        (SETQ PTDATUM2(LIST CXDATUM2 CYDATUM1))
        (COMMAND "LINE" PTDATUM1 PTDATUM2 *CANCEL*)

        (SETQ PTTEXT(LIST(* 30 -0.45)(+ 0.1 (NTH 1 PTDATUM1))))
        (SETQ NOTE (STRCAT "%%BDATUM LEVEL-%%B" (RTOS DATUM 2 3) "%%BM%%B"))
        (COMMAND "TEXT" PTTEXT 0.6 "0" NOTE)

(SETQ PTNSL1(LIST(NTH 0 PTDATUM1)(- (NTH 1 PTDATUM1) 2)))
        (SETQ PTNSL2(LIST(NTH 0 PTDATUM2)(NTH 1 PTNSL1)))
        (COMMAND "LINE" PTNSL1 PTNSL2 *CANCEL*)

        (SETQ PTTEXT(LIST(* 30 -0.45)(+ 0.1 (NTH 1 PTNSL1))))
        (SETQ NOTE (STRCAT "%%BNATURAL SOIL LEVEL M %%B" " "))
        (COMMAND "TEXT" PTTEXT 0.6 "0" NOTE)

(SETQ PTGRADIENT1(LIST(NTH 0 PTDATUM1)(- (NTH 1 PTNSL2) 2)))
        (SETQ PTGRADIENT2(LIST(NTH 0 PTDATUM2)(NTH 1 PTGRADIENT1)))
        (COMMAND "LINE" PTGRADIENT1 PTGRADIENT2 *CANCEL*)

        (SETQ PTTEXT(LIST(* 30 -0.45)(+ 0.1 (NTH 1 PTGRADIENT1))))
        (SETQ NOTE (STRCAT "%%BGRADIENT %%B" ""))
        (COMMAND "TEXT" PTTEXT 0.6 "0" NOTE)




(SETQ PTFORMATION1(LIST(NTH 0 PTDATUM1)(- (NTH 1 PTGRADIENT2) 2)))
        (SETQ PTFORMATION2(LIST(NTH 0 PTDATUM2)(NTH 1 PTFORMATION1)))
        (COMMAND "LINE" PTFORMATION1 PTFORMATION2 *CANCEL*)

        (SETQ PTTEXT(LIST(* 30 -0.45)(+ 0.1 (NTH 1 PTFORMATION1))))
        (SETQ NOTE (STRCAT "%%BFORMATION LEVEL M %%B" ""))
        (COMMAND "TEXT" PTTEXT 0.6 "0" NOTE)




(SETQ PTCHAINAGE1(LIST(NTH 0 PTDATUM1)(- (NTH 1 PTFORMATION2) 2)))
        (SETQ PTCHAINAGE2(LIST(NTH 0 PTDATUM2)(NTH 1 PTCHAINAGE1)))
        (COMMAND "LINE" PTCHAINAGE1 PTCHAINAGE2 *CANCEL*)

        (SETQ PTTEXT(LIST(* 30 -0.45)(+ 0.1 (NTH 1 PTCHAINAGE1))))
        (SETQ NOTE (STRCAT "%%BCHAINAGE IN M %%B" ""))
        (COMMAND "TEXT" PTTEXT 0.6 "0" NOTE)


(SETQ PTTEXT(LIST(NTH 0 PTX)(NTH 1 PTNSL1)))
        (SETQ NOTE (STRCAT "-" (RTOS NSL 2 3)))
        (COMMAND "TEXT" PTTEXT 0.3 "90" NOTE)
(SETQ PTTEXT1(LIST(NTH 0 PTX)(NTH 1 PTCHAINAGE1)))
        (SETQ NOTE (STRCAT "-" (RTOS 0 2 0)))
        (COMMAND "TEXT" PTTEXT1 0.3 "90" NOTE)

(REPEAT NOFPOINT
        (SETQ X(+ X 1))
        (SETQ NSL(GETREAL "GIVE NSL OF NEXT POINT IN M;"))  
        (SETQ CX (/ (* INTERVAL X) 10))
        (SETQ CY (- NSL DATUM))
        (SETQ PT1(LIST(NTH 0 PTX)(NTH 1 PTX)))
        (SETQ PT2(LIST CX CY))
        (COMMAND "LINE" PT1 PT2 *CANCEL*)
        (SETQ PTX(LIST(NTH 0 PT2)(NTH 1 PT2)))
        (SETQ PTTEXT(LIST(NTH 0 PT2)(NTH 1 PTNSL1)))
        (SETQ NOTE (STRCAT "-" (RTOS NSL 2 3)))
        (COMMAND "TEXT" PTTEXT 0.3 "90" NOTE)

        (SETQ PTTEXT1(LIST(NTH 0 PT2)(NTH 1 PTCHAINAGE1)))
        (SETQ NOTE (STRCAT "-" (RTOS (* 10 CX) 2 0)))
        (COMMAND "TEXT" PTTEXT1 0.3 "90" NOTE)
                 )
(COMMAND "ZOOM" "EXTENTS" "ZOOM" "VMAX")

   )
