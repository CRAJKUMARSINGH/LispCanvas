(DEFUN C:ROADX()
(SETQ FW(GETREAL "GIVE VALUE OF WIDTH OF FORMATION OF ROAD IN M;"))
(SETQ CW(GETREAL "GIVE VALUE OF WIDTH OF CARRIAGEWAY OF ROAD IN M;"))
(SETQ MAXLEVEL(GETREAL "GIVE MAXIMUM LEVEL IN M;"))
(SETQ MINLEVEL(GETREAL "GIVE MINIMUM LEVEL IN M;"))
(SETQ POINTSL(GETINT "GIVE NUMBER OF POINTS OF SURVEY ON LEFT SIDE;"))
(SETQ POINTSR(GETINT "GIVE NUMBER OF POINTS OF SURVEY ON RIGHT SIDE;"))
(SETQ NSL(GETREAL "GIVE NSL OF CENTRE POINT IN M;"))
(SETQ FL(GETREAL "GIVE FORMATION LEVEL OF CENTRE POINT IN M;"))
(SETQ DAT1(FIX MINLEVEL ))
(SETQ DAT2(FIX (/ MINLEVEL 10)))
(SETQ DAT3(FIX (- DAT1 (* 10 DAT2))))
(SETQ DAT4(FIX (/ DAT3 5)))
(SETQ DATUM(FIX (+ (* DAT2 10) (* 5 DAT4))))
(SETQ CamberC(GETREAL "GIVE VALUE OF CAMBER IN CARRIAGEWAY IN % ;"))
(SETQ CamberS(GETREAL "GIVE VALUE OF CAMBER IN SHOULDERS IN % ;"))
(SETQ SIDESLOPE(GETREAL "GIVE VALUE OF SIDE SLOPE IN n : 1 VALUE OF n IS ;"))
        (SETQ CYF (- FL DATUM))
        (SETQ SW (/ (- FW CW) 2))
        (SETQ PTFC(LIST 0 CYF))
        (SETQ PTFL1(LIST(- (NTH 0 PTFC) (/ CW 2))(- (NTH 1 PTFC) (/ (* CamberC CW) 200))))
        (SETQ PTFL2(LIST(- (NTH 0 PTFC) (/ FW 2))(- (NTH 1 PTFL1) (/ (* CamberS SW) 200))))
        (SETQ R(* SIDESLOPE (- (NTH 1 PTFL2) 0)))
        (SETQ PTFL3(LIST(- (NTH 0 PTFL2) R) 0))
        (SETQ PTFR1(LIST(+ (NTH 0 PTFC) (/ CW 2))(NTH 1 PTFL1)))
        (SETQ PTFR2(LIST(+ (NTH 0 PTFC) (/ FW 2))(NTH 1 PTFL2)))
        (SETQ PTFR3(LIST(+ (NTH 0 PTFR2) R) 0))
        (COMMAND "LINE" PTFL3 PTFL2 PTFL1 PTFC PTFR1 PTFR2 PTFR3 *CANCEL*)
(SETQ CYN (- NSL DATUM))
(SETQ PTCN(LIST 0 CYN))      
        (SETQ PTVERTICAL1(LIST (NTH 0 PTFL3) -8))
        (SETQ PTVERTICAL2(LIST (NTH 0 PTFL3) (- MAXLEVEL DATUM)))
        (COMMAND "LINE" PTVERTICAL1 PTVERTICAL2 *CANCEL*)      

        (SETQ CYDATUM1 (FLOAT 0))
        (SETQ PTDATUM1(LIST (- (NTH 0 PTFL3) 15) CYDATUM1))
        (SETQ PTDATUM2(LIST (NTH 0 PTFR3) CYDATUM1))
        (COMMAND "LINE" PTDATUM1 PTDATUM2 *CANCEL*)

        (SETQ PTTEXT(LIST(NTH 0 PTDATUM1)(+ 0.1 (NTH 1 PTDATUM1))))
        (SETQ NOTE (STRCAT "%%BDATUM LEVEL-%%B" (RTOS DATUM 2 3) "%%BM%%B"))
        (COMMAND "TEXT" PTTEXT 0.6 "0" NOTE)

(SETQ PTNSL1(LIST(NTH 0 PTDATUM1)(- (NTH 1 PTDATUM1) 2)))
        (SETQ PTNSL2(LIST(NTH 0 PTDATUM2)(NTH 1 PTNSL1)))
        (COMMAND "LINE" PTNSL1 PTNSL2 *CANCEL*)

        (SETQ PTTEXT(LIST(NTH 0 PTDATUM1)(+ 0.1 (NTH 1 PTNSL1))))
        (SETQ NOTE (STRCAT "%%BNATURAL SOIL LEVEL M %%B" " "))
        (COMMAND "TEXT" PTTEXT 0.6 "0" NOTE)   

(SETQ PTFORMATION1(LIST(NTH 0 PTDATUM1)(- (NTH 1 PTNSL2) 2)))
        (SETQ PTFORMATION2(LIST(NTH 0 PTDATUM2)(NTH 1 PTFORMATION1)))
        (COMMAND "LINE" PTFORMATION1 PTFORMATION2 *CANCEL*)

        (SETQ PTTEXT(LIST(NTH 0 PTDATUM1)(+ 0.1 (NTH 1 PTFORMATION1))))
        (SETQ NOTE (STRCAT "%%BFORMATION LEVEL M %%B" ""))
        (COMMAND "TEXT" PTTEXT 0.6 "0" NOTE)

(SETQ PTCHAINAGE1(LIST(NTH 0 PTDATUM1)(- (NTH 1 PTFORMATION2) 2)))
        (SETQ PTCHAINAGE2(LIST(NTH 0 PTDATUM2)(NTH 1 PTCHAINAGE1)))
        (COMMAND "LINE" PTCHAINAGE1 PTCHAINAGE2 *CANCEL*)

        (SETQ PTTEXT(LIST(NTH 0 PTDATUM1)(+ 0.1 (NTH 1 PTCHAINAGE1))))
        (SETQ NOTE (STRCAT "%%BDISTANCE FROM CENTRE IN M%%B" ""))
        (COMMAND "TEXT" PTTEXT 0.6 "0" NOTE)

(SETQ PTTEXT(LIST(NTH 0 PTCN)(NTH 1 PTNSL1)))
        (SETQ NOTE (STRCAT "-" (RTOS NSL 2 3)))
        (COMMAND "TEXT" PTTEXT 0.3 "90" NOTE)
(SETQ PTTEXT(LIST(NTH 0 PTCN)(NTH 1 PTFORMATION1)))
        (SETQ NOTE (STRCAT "-" (RTOS FL 2 3)))
        (COMMAND "TEXT" PTTEXT 0.3 "90" NOTE)

(SETQ PTTEXT1(LIST(NTH 0 PTCN)(NTH 1 PTCHAINAGE1)))
        (SETQ NOTE (STRCAT "-" (RTOS 0 2 0)))
        (COMMAND "TEXT" PTTEXT1 0.3 "90" NOTE)
(SETQ X (FIX 0))
(SETQ PTXL(LIST(NTH 0 PTCN)(NTH 1 PTCN)))      
(SETQ PTXR(LIST(NTH 0 PTCN)(NTH 1 PTCN)))

        (REPEAT POINTSL
                (SETQ X(+ X 1))
                (SETQ DL(GETREAL "GIVE DISTANCE OF NEXT POINT ON LEFT SIDE IN M;"))
                (SETQ NSL(GETREAL "GIVE NSL OF THIS LEFT POINT IN M;"))  
                (SETQ CXL (- 0 DL))
                (SETQ CYL (- NSL DATUM))
                (SETQ PTL1(LIST(NTH 0 PTXL)(NTH 1 PTXL)))    
                (SETQ PTL2(LIST CXL CYL))
                (COMMAND "LINE" PTL1 PTL2 *CANCEL*)
                (SETQ PTXL(LIST(NTH 0 PTL2)(NTH 1 PTL2)))
                (SETQ PTTEXT(LIST(NTH 0 PTL2)(NTH 1 PTNSL1)))
                (SETQ NOTE (STRCAT "-" (RTOS NSL 2 3)))
                (COMMAND "TEXT" PTTEXT 0.3 "90" NOTE)
                (SETQ PTTEXT1(LIST(NTH 0 PTL2)(NTH 1 PTCHAINAGE1)))
                (SETQ NOTE (STRCAT "-" (RTOS DL 2 0)))
                (COMMAND "TEXT" PTTEXT1 0.3 "90" NOTE)
                )
        (SETQ X (FIX 0))
        (REPEAT POINTSR
                (SETQ X(+ X 1))
                (SETQ DR(GETREAL "GIVE DISTANCE OF NEXT POINT ON RIGHT SIDE IN M;"))
                (SETQ NSR(GETREAL "GIVE NSL OF THIS RIGHT POINT IN M;"))  
                (SETQ CYR (- NSL DATUM))
                (SETQ PTR1(LIST(NTH 0 PTXR)(NTH 1 PTXR)))
                (SETQ PTR2(LIST DL CYR))
                (COMMAND "LINE" PTR1 PTR2 *CANCEL*)
                (SETQ PTXR(LIST(NTH 0 PTR2)(NTH 1 PTR2)))
                (SETQ PTTEXT(LIST(NTH 0 PTR2)(NTH 1 PTNSL1)))
                (SETQ NOTE (STRCAT "-" (RTOS NSL 2 3)))
                (COMMAND "TEXT" PTTEXT 0.3 "90" NOTE)
                (SETQ PTTEXT1(LIST(NTH 0 PTR2)(NTH 1 PTCHAINAGE1)))
                (SETQ NOTE (STRCAT "-" (RTOS DR 2 0)))
                (COMMAND "TEXT" PTTEXT1 0.3 "90" NOTE)
                 )
(COMMAND "ZOOM" "EXTENTS" "ZOOM" "VMAX")
(SETQ FW 0)
(SETQ CW 0)
(SETQ MAXLEVEL 0)
(SETQ MINLEVEL 0)
(SETQ POINTSL 0)
(SETQ POINTSR 0)
(SETQ NSL 0)
(SETQ FL 0)

                 )
