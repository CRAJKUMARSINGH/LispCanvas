(DEFUN C:SUNSHADE()

  (SETQ DIMTEXT 150)
  ;Text height

  (SETQ DIMTXSTY "NEW" RAJ150 "ARIAL" REGULAR "CANCEL")
  ;Text style
  (SETQ DIMASZ 15)
 (SETQ DIMALTD 0)
(SETQ DIMRND 0)
  ;     Rounding value
DIMSAH      Off                  Separate arrow blocks
(SETQ DIMSCALE 1.0000)
  ;Overall scale factor
  
;(SETQ B(GETINT "GIVE VALUE OF WEB WIDTH IN MM;"))
;(SETQ D(GETINT "GIVE VALUE OF TOTAL DEPTH IN MM;"))
;(SETQ PROJ(GETINT "GIVE VALUE OF PROJECTION OF THE SUNSHADE IN MM;"))
;(SETQ THICKSUP(GETINT "GIVE VALUE OF SUNSHADE THICKNESS NEAR SUPPORT IN MM;"))
;(SETQ THICKEDG(GETINT "GIVE VALUE OF SUNSHADE THICKNESS AT THE OUTER EDGE IN MM;"))
;(SETQ DIAB(GETINT "GIVE DIA OF BOTTOM BARS IN MM;"))
;(SETQ NBB(GETINT "GIVE NUMBER OF BOTTOM BARS ;"))
;(SETQ DIAT(GETINT "GIVE DIA OF TOP BARS IN MM;"))
;(SETQ NBT(GETINT "GIVE NUMBER OF TOP BARS ;"))
;(SETQ DIAS(GETINT "GIVE DIA OF SHEAR STIRRUPS BARS IN MM;"))
;(SETQ SPC(GETINT "GIVE SPACING OF SHEAR STIRRUPS IN MM;"))
;(SETQ DIASMAIN(GETINT "GIVE DIA OF SUNSHADE MAIN BARS IN MM;"))
;(SETQ DIASDIS(GETINT "GIVE DIA OF SUNSHADE DISTRIBUTION BARS IN MM;"))
;(SETQ SPCDIS(GETINT "GIVE SPACING OF SUNSHADE DISTRIBUTION BARS IN MM;"))
;(SETQ SUNSHADENUM(GETSTRING "GIVE SUNSHADE NUMBER ;"))
;(SETQ PT1(GETPOINT "PICK FIRST CORNER OF THE SUNSHADE ;"))



  
(SETQ B 300)
  (SETQ D 200)
  (SETQ PROJ 600)
  (SETQ THICKSUP 150)
  (SETQ THICKEDG 50)
  
(SETQ DIAB 12)
(SETQ NBB 3)
(SETQ DIAT 10)
(SETQ NBT 2)
(SETQ DIAS 8)
(SETQ SPC 150)
(SETQ DIASMAIN 8)
(SETQ DIASDIS 8)
(SETQ SPCDIS 150)
(SETQ SUNSHADENUM RAJ15)

(SETQ PT1(LIST 150 150))
  
(SETQ PT2(LIST(+ (NTH 0 PT1) B)(NTH 1 PT1)))
(SETQ PT3(LIST(NTH 0 PT2)(+ (NTH 1 PT2) D)))
(SETQ PT4(LIST(NTH 0 PT1)(NTH 1 PT3)))
(SETQ PT201(LIST(+ (NTH 0 PT1) 25)(+ (NTH 1 PT1) 25)))
(SETQ PT202(LIST(- (NTH 0 PT2) 25)(NTH 1 PT201)))
(SETQ PT203(LIST(NTH 0 PT202)(- (NTH 1 PT3) 25)))
(SETQ PT204(LIST(NTH 0 PT201)(NTH 1 PT203)))
(SETQ DDASB(+ 25 (/ DIAB 2)))
(SETQ DDAST(+ 25 (/ DIAT 2)))
(SETQ PT5(LIST(+ (NTH 0 PT1) DDASB)(+ (NTH 1 PT1) DDASB)))
(SETQ PT6(LIST(+ (NTH 0 PT1) DDAST)(- (NTH 1 PT4) DDAST)))
(SETQ PTC1(LIST(+ (NTH 0 PT5) (* 0.3 DIAB))(NTH 1 PT5)))
(SETQ PTC2(LIST(+ (NTH 0 PT6) (* 0.25 DIAT))(NTH 1 PT6)))
(SETQ PT6(LIST(+ (NTH 0 PT1) DDAST)(- (NTH 1 PT4) DDAST)))
(SETQ PT105(LIST(NTH 0 PT2)(+ (NTH 1 PT2) THICKSUP)))
(SETQ PT106(LIST(NTH 0 PT2)(NTH 1 PT2)))
(SETQ PT107(LIST(+ (NTH 0 PT105) PROJ)(+ (NTH 1 PT2) THICKEDG)))
(SETQ PT108(LIST(NTH 0 PT107)(NTH 1 PT2)))
(SETQ PT201(LIST(+ (NTH 0 PT1) 25)(+ (NTH 1 PT1) 25)))
(SETQ PT202(LIST(- (NTH 0 PT2) 25)(NTH 1 PT201)))
(SETQ PT203(LIST(NTH 0 PT202)(- (NTH 1 PT3) 25)))
(SETQ PT204(LIST(NTH 0 PT201)(NTH 1 PT203)))
(SETQ PT205(LIST(NTH 0 PT202)(+ (NTH 1 PT202) PROJ)))
(SETQ PT206(LIST(NTH 0 PT205)(+ (NTH 1 PT205) (- THICKEDG 50))))
(SETQ SPACINGB(/ (- B (* 2 DDASB)) (- NBB 1)))
(SETQ SPACINGT(/ (- B (* 2 DDAST)) (- NBT 1)))
(COMMAND "ZOOM" "C" PTC1 250)
(COMMAND "DONUT" 0 DIAB PT5 NIL)
(COMMAND "ZOOM" "C" PTC1 250)
(COMMAND "DONUT" 0 DIAT PT6 NIL)
(SETQ PTD1(LIST(NTH 0 PT1)(- (NTH 1 PT1) (* 1.2 DIMTEXT))))
(SETQ PTD111(LIST(NTH 0 PT2)(- (NTH 1 PT1) (* 1.2 DIMTEXT))))
(SETQ PTD2(LIST(- (NTH 0 PT1) (* 1.5 DIMTEXT))(NTH 1 PT1)))
(SETQ PTD3(LIST(NTH 0 PT5)(NTH 1 PT5)))
(SETQ PTD4(LIST(NTH 0 PTD3)(+ (NTH 1 PTD3) (* 0.25 D))))
(SETQ PTD5(LIST(+ (NTH 0 PTD4) B)(NTH 1 PTD4)))
(SETQ PTD6(LIST(NTH 0 PT6)(NTH 1 PT6)))
(SETQ PTD7(LIST(NTH 0 PTD6)(+ (NTH 1 PTD5) (* 0.35 D))))
(SETQ PTC1(LIST(+ (NTH 0 PT5) (* 0.3 DIAB))(NTH 1 PT5)))
(SETQ PTC2(LIST(+ (NTH 0 PT6) (* 0.25 DIAT))(NTH 1 PT6)))
(COMMAND "ZOOM" "C" PTC1 250)

(COMMAND "ARRAY" "SINGLE" PTC1 "RECTANGULAR" "1" NBB SPACINGB)
(COMMAND "LINE" PTD3 PTD4 *CANCEL*)
(COMMAND "ZOOM" "C" PTD4 250)
(COMMAND "ARRAY" "SINGLE" PTD4 "RECTANGULAR" "1" NBB SPACINGB)
(SETQ PTD8(LIST(+ (NTH 0 PTD7) B)(NTH 1 PTD7)))
(COMMAND "ZOOM" "C" PTC2 250)
(COMMAND "ARRAY" "SINGLE" PTC2 "RECTANGULAR" "1" NBT SPACINGT)
(COMMAND "LINE" PTD6 PTD7 *CANCEL*)
(COMMAND "ZOOM" "C" PTC1 250)
(COMMAND "ARRAY" "SINGLE" PTD7 "RECTANGULAR" "1" NBT SPACINGT)
(COMMAND "PLINE" PT201 PT202 PT203 PT204 "C")
(COMMAND "PLINE" PT1 PT108 PT107 PT105 PT3  PT4 "C" *CANCLE*)
(COMMAND "DIM" "HORIZONTAL" PT1 PT2 "T" B PTD1 *CANCLE*)
(COMMAND "DIM" "HORIZONTAL" PT2 PT108 "T" PROJ PTD111 *CANCLE*)
(COMMAND "DIM" "VERTICAL" PT1 PT4 "T" D PTD2 *CANCEL*)
(SETQ PTD101(LIST(+ (NTH 0 PT108) THICKSUP)(NTH 1 PT108)))
(SETQ PTD102(LIST(+ (NTH 0 PTD101) (* 1 DIMTEXT))(NTH 1 PTD101)))
(SETQ PT105DAS(LIST(+ (NTH 0 PT105) (+ PROJ THICKSUP))(NTH 1 PT105)))
(SETQ PT106DAS(LIST(NTH 0 PT105DAS)(NTH 1 PT106)))
(COMMAND "DIM" "VERTICAL" PT105DAS PT106DAS "T" THICKSUP PTD101 *CANCEL*)
(COMMAND "DIM" "VERTICAL" PT107 PT108 "T" THICKEDG PTD102 *CANCEL*)
(SETQ PTD9(LIST(- (NTH 0 PT2) 25)(+ (NTH 1 PTD5) (* 0.2 D))))
(SETQ PTD10(LIST(NTH 0 PTD5)(NTH 1 PTD9)))
(COMMAND "LINE" PTD4 PTD5 *CANCEL*)
(COMMAND "LINE" PTD7 PTD8 *CANCEL*)
(COMMAND "LINE" PTD9 PTD10 *CANCEL*)
(SETQ NOTE (STRCAT (ITOA NBB) "NOS." (ITOA DIAB) "MM DIA.TOR BARS"))
(COMMAND "TEXT" PTD5 (* 0.1 D) "0" NOTE)
(SETQ NOTE (STRCAT (ITOA NBT) "NOS." (ITOA DIAT) "MM DIA.TOR BARS"))
(COMMAND "TEXT" PTD8 (* 0.1 D) "0" NOTE)
(SETQ NOTE (STRCAT (ITOA DIAS) "MM DIA.TWO LEGGED STIRRUPS @" (ITOA SPC) "MM C/C."))
(COMMAND "TEXT" PTD10 (* 0.1 D) "0" NOTE)
(SETQ PTD11(LIST(NTH 0 PT1)(- (NTH 1 PT1) (* 4 DIMTEXT))))
(SETQ NOTE (STRCAT "%%USUNSHADE NO.SS-%%U" SUNSHADENUM))
(COMMAND "TEXT" PTD11 (* 0.125 D) "0" NOTE)

(COMMAND "ZOOM" "C" PTD10 (* 3.5 D))
(SETQ R1(+ B PROJ))
(SETQ R2(FLOAT(- R1 50)))
(SETQ R3(FLOAT(- THICKSUP THICKEDG)))
(SETQ R4(FLOAT(/ R3 PROJ)))
(SETQ R(* R2 R4))
(SETQ PT503(LIST(- (NTH 0 PT108) 25)(+ (NTH 1 PT108) 25)))
(SETQ PT502(LIST(NTH 0 PT503)(- (NTH 1 PT107) 25)))
(SETQ PT501(LIST(NTH 0 PT201)(+ (NTH 1 PT502) R)))
(COMMAND "LINE" PT501 PT502 PT503 *CANCLE*)
(SETQ VCOMPONENT(* R4 SPCDIS))
(SETQ PTDONUT1(LIST(- (NTH 0 PT502) (/ DIASDIS 2))(- (NTH 1 PT502) (/ DIASDIS 2))))
(SETQ PTDONUT2(LIST(- (NTH 0 PTDONUT1) SPCDIS)(+ (NTH 1 PTDONUT1) VCOMPONENT)))
(SETQ PTDONUT3(LIST(- (NTH 0 PTDONUT2) SPCDIS)(+ (NTH 1 PTDONUT2) VCOMPONENT)))
(SETQ PTDONUT4(LIST(- (NTH 0 PTDONUT3) SPCDIS)(+ (NTH 1 PTDONUT3) VCOMPONENT)))
(SETQ PTDONUT5(LIST(- (NTH 0 PTDONUT4) SPCDIS)(+ (NTH 1 PTDONUT4) VCOMPONENT)))
(SETQ PTDONUT6(LIST(- (NTH 0 PTDONUT5) SPCDIS)(+ (NTH 1 PTDONUT5) VCOMPONENT)))
(SETQ PTDONUT7(LIST(- (NTH 0 PTDONUT6) SPCDIS)(+ (NTH 1 PTDONUT6) VCOMPONENT)))
(SETQ PTDONUT8(LIST(- (NTH 0 PTDONUT7) SPCDIS)(+ (NTH 1 PTDONUT7) VCOMPONENT)))
(SETQ PTDONUT9(LIST(- (NTH 0 PTDONUT8) SPCDIS)(+ (NTH 1 PTDONUT8) VCOMPONENT)))
(COMMAND "DONUT" 0 DIASDIS PTDONUT1 *CANCLE*)
(COMMAND "DONUT" 0 DIASDIS PTDONUT2 *CANCLE*)
(COMMAND "DONUT" 0 DIASDIS PTDONUT3 *CANCLE*)
(COMMAND "DONUT" 0 DIASDIS PTDONUT4 *CANCLE*)
(SETQ NODIS(+ (/ PROJ SPCDIS) 1))
(IF (> NODIS 4) (COMMAND "DONUT" 0 DIASDIS PTDONUT5 *CANCLE*) *CANCLE*)
(IF (> NODIS 5) (COMMAND "DONUT" 0 DIASDIS PTDONUT6 *CANCLE*) *CANCLE*)
(IF (> NODIS 6) (COMMAND "DONUT" 0 DIASDIS PTDONUT7 *CANCLE*) *CANCLE*)
(IF (> NODIS 7) (COMMAND "DONUT" 0 DIASDIS PTDONUT8 *CANCLE*) *CANCLE*)
(IF (> NODIS 8) (COMMAND "DONUT" 0 DIASDIS PTDONUT9 *CANCLE*) *CANCLE*)
;(_AI_SELALL "CANCEL")

)
