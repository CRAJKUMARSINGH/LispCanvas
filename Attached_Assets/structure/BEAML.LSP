(DEFUN C:BEAML()
(SETQ B(GETINT "GIVE VALUE OF WEB WIDTH IN MM;"))
(SETQ D(GETINT "GIVE VALUE OF TOTAL DEPTH IN MM;"))
(SETQ DFT(GETINT "GIVE VALUE OF TOP FLANGE THICKNESS IN MM;"))
(SETQ DFB(GETINT "GIVE VALUE OF BOTTOM FLANGE THICKNESS IN MM;"))
(SETQ DIAB(GETINT "GIVE DIA OF BOTTOM BARS IN MM;"))
(SETQ NBB(GETINT "GIVE NUMBER OF BOTTOM BARS ;"))
(SETQ DIAT(GETINT "GIVE DIA OF TOP BARS IN MM;"))
(SETQ NBT(GETINT "GIVE NUMBER OF TOP BARS ;"))
(SETQ DIAS(GETINT "GIVE DIA OF SHEAR STIRRUPS BARS IN MM;"))
(SETQ SPC(GETINT "GIVE SPACING OF SHEAR STIRRUPS IN MM;"))
(SETQ SCALE(GETINT "GIVE DRAWING SCALE 1: ?  ;"))
(SETQ BEAMNUM(GETSTRING "GIVE BEAM NUMBER ;"))
(SETQ DIMTEXT (* 3 SCALE))
(SETQ PT1(GETPOINT "PICK FIRST CORNER OF THE BEAM ;"))
(SETQ PT2(LIST(+ (NTH 0 PT1) B)(NTH 1 PT1)))
(SETQ PT3(LIST(NTH 0 PT2)(+ (NTH 1 PT2) D)))
(SETQ PT4(LIST(NTH 0 PT1)(NTH 1 PT3)))
(SETQ PT201(LIST(+ (NTH 0 PT1) 25)(+ (NTH 1 PT1) 25)))
(SETQ PT202(LIST(- (NTH 0 PT2) 25)(NTH 1 PT201)))
(SETQ PT203(LIST(NTH 0 PT202)(- (NTH 1 PT3) 25)))
(SETQ PT204(LIST(NTH 0 PT201)(NTH 1 PT203)))
(SETQ DDASB (+ 25 (/ DIAB 2)))
(SETQ DDAST (+ 25 (/ DIAT 2)))
(SETQ PT5(LIST(+ (NTH 0 PT1) DDASB)(+ (NTH 1 PT1) DDASB)))
(SETQ PT6(LIST(+ (NTH 0 PT1) DDAST)(- (NTH 1 PT4) DDAST)))
(SETQ PTC1(LIST(+ (NTH 0 PT5) (* 0.25 DIAB))(NTH 1 PT5)))
(SETQ PTC2(LIST(+ (NTH 0 PT6) (* 0.25 DIAT))(NTH 1 PT6)))
(SETQ PT6(LIST(+ (NTH 0 PT1) DDAST)(- (NTH 1 PT4) DDAST)))
(SETQ SPACINGB (/ (- B (* 2 DDASB)) (- NBB 1)))
(SETQ SPACINGT (/ (- B (* 2 DDAST)) (- NBT 1)))
(COMMAND "DONUT" 0 DIAB PT5 NIL)
(COMMAND "DONUT" 0 DIAT PT6 NIL)
(SETQ PTD1(LIST(NTH 0 PT1)(- (NTH 1 PT1) (* 1.2 DIMTEXT))))
(SETQ PTD2(LIST(- (NTH 0 PT1) (* 1.5 DIMTEXT))(NTH 1 PT1)))
(SETQ PTD3(LIST(NTH 0 PT5)(NTH 1 PT5)))
(SETQ PTD4(LIST(NTH 0 PTD3)(+ (NTH 1 PTD3) (* 0.25 D))))
(SETQ PTD5(LIST(+ (NTH 0 PTD4) B)(NTH 1 PTD4)))
(SETQ PTD6(LIST(NTH 0 PT6)(NTH 1 PT6)))
(SETQ PTD7(LIST(NTH 0 PTD6)(+ (NTH 1 PTD5) (* 0.35 D))))
(COMMAND "ARRAY" "SI" PTC1 "R" "1" NBB SPACINGB)
(COMMAND "LINE" PTD3 PTD4 *CANCEL*)
(COMMAND "ARRAY" "SI" PTD4 "R" "1" NBB SPACINGB)
(SETQ PTD8(LIST(+ (NTH 0 PTD7) B)(NTH 1 PTD7)))
(COMMAND "ARRAY" "SI" PTC2 "R" "1" NBT SPACINGT)
(COMMAND "LINE" PTD6 PTD7 *CANCEL*)
(COMMAND "ARRAY" "SI" PTD7 "R" "1" NBT SPACINGT)
(COMMAND "PLINE" PT201 PT202 PT203 PT204 "C")
(SETQ PT101(LIST(NTH 0 PT4)(NTH 1 PT4)))
(SETQ PT102(LIST(NTH 0 PT101)(- (NTH 1 PT101) DFT)))
(SETQ PT1012(LIST(NTH 0 PT101)(- (NTH 1 PT101) (/ DFT 2))))
(SETQ PT103(LIST(- (NTH 0 PT101) (* 3 B))(NTH 1 PT101)))
(SETQ PT104(LIST(NTH 0 PT103)(- (NTH 1 PT103) DFT)))
(SETQ EXT1(/ DFT 4))
(SETQ EXT2(/ DFT 2))
(SETQ PTEL101(LIST(NTH 0 PT103)(+ (NTH 1 PT103) EXT1)))
(SETQ PTEL102(LIST(NTH 0 PT103)(NTH 1 PT103)))
(SETQ PTEL103(LIST(NTH 0 PTEL101)(- (NTH 1 PTEL102) EXT1)))
(SETQ PTEL104(LIST(+ (NTH 0 PTEL103) EXT1)(NTH 1 PTEL103)))
(SETQ PTEL105(LIST(- (NTH 0 PTEL103) EXT1)(- (NTH 1 PTEL103) EXT2)))
(SETQ PTEL106(LIST(NTH 0 PTEL103)(- (NTH 1 PTEL103) EXT2)))
(SETQ PTEL107(LIST(NTH 0 PT104)(NTH 1 PT104)))
(SETQ PTEL108(LIST(NTH 0 PTEL107)(- (NTH 1 PTEL107) EXT1)))
(COMMAND "LINE" PTEL101 PTEL102 PTEL103 PTEL104 PTEL105 PTEL106 PTEL107 PTEL108 *CANCEL*)
(SETQ PT105(LIST(NTH 0 PT3)(+ (NTH 1 PT2) DFB)))
(SETQ PT106(LIST(NTH 0 PT2)(NTH 1 PT2)))
(SETQ PT107(LIST(+ (NTH 0 PT105) (* 3 B))(NTH 1 PT105)))
(SETQ PT108(LIST(NTH 0 PT107)(NTH 1 PT2)))
(SETQ EXT1(/ DFB 4))
(SETQ EXT2(/ DFB 2))
(SETQ PTER101(LIST(NTH 0 PT107)(+ (NTH 1 PT107) EXT1)))
(SETQ PTER102(LIST(NTH 0 PT107)(NTH 1 PT107)))
(SETQ PTER103(LIST(NTH 0 PTER101)(- (NTH 1 PTER102) EXT1)))
(SETQ PTER104(LIST(+ (NTH 0 PTER103) EXT1)(NTH 1 PTER103)))
(SETQ PTER105(LIST(- (NTH 0 PTER103) EXT1)(- (NTH 1 PTER103) EXT2)))
(SETQ PTER106(LIST(NTH 0 PTER103)(- (NTH 1 PTER103) EXT2)))
(SETQ PTER107(LIST(NTH 0 PT108)(NTH 1 PT108)))
(SETQ PTER108(LIST(NTH 0 PTER107)(- (NTH 1 PTER107) EXT1)))
(COMMAND "LINE" PTER101 PTER102 PTER103 PTER104 PTER105 PTER106 PTER107 PTER108 *CANCEL*)
(COMMAND "LINE" PT104 PT102 PT1 PT108 *CANCLE*)
(COMMAND "LINE" PT103 PT3 PT105 PT107 *CANCEL*)
(COMMAND "DIM" "HORIZONTAL" PT1 PT2 "T" B PTD1 *CANCLE*)
(COMMAND "DIM" "VERTICAL" PT1 PT4 "T" D PTD2 *CANCEL*)
(SETQ PTD101(LIST(- (NTH 0 PTEL103) DFT)(NTH 1 PT103)))
(SETQ PTD102(LIST(+ (NTH 0 PTER103) DFB)(NTH 1 PTER103)))
(COMMAND "DIM" "VERTICAL" PTEL102 PTEL107 "T" DFT PTD101 *CANCEL*)
(COMMAND "DIM" "VERTICAL" PTER102 PTER107 "T" DFB PTD102 *CANCEL*)
(SETQ PTD9(LIST(- (NTH 0 PT2) 25)(+ (NTH 1 PTD5) (* 0.2 D))))
(SETQ PTD10(LIST(NTH 0 PTD5)(NTH 1 PTD9)))
(COMMAND "LINE" PTD4 PTD5 *CANCEL*)
(COMMAND "LINE" PTD7 PTD8 *CANCEL*)
(COMMAND "LINE" PTD9 PTD10 *CANCEL*)
(SETQ NOTE (STRCAT (ITOA NBB) "NOS." (ITOA DIAB) "MM DIA.TOR BARS"))
(COMMAND "TEXT" PTD5 (* 0.1 D) "0" NOTE)
(SETQ NOTE (STRCAT (ITOA NBT) "NOS." (ITOA DIAT) "MM DIA.TOR BARS"))
(COMMAND "TEXT" PTD8 (* 0.1 D) "0" NOTE)
(SETQ NOTE (STRCAT (ITOA DIAS) "MM DIA.TWO LEGGED STIRRUPS @" (ITOA SPC) "MM C/C."))
(COMMAND "TEXT" PTD10 (* 0.1 D) "0" NOTE)
(SETQ PTD11(LIST(NTH 0 PT1)(- (NTH 1 PT1) (* 4 DIMTEXT))))
(SETQ NOTE (STRCAT "%%UBEAM NO.B-%%U" BEAMNUM))
(COMMAND "TEXT" PTD11 (* 0.125 D) "0" NOTE)
(COMMAND "ZOOM" "C" PTD10 (* 3.5 D))
(SETQ PT1(LIST(NTH 0 PT1)(+ (NTH 1 PT4) (* 4 DIMTEXT))))
)
