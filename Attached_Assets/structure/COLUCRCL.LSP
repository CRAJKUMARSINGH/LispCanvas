(DEFUN C:COLUCRCL()
(SETQ D(GETINT "GIVE VALUE OF DIAMETER OF THE COLUMN IN MM;"))
(SETQ DIAL(GETINT "GIVE DIA OF LONGITUDINAL REINFORCEMENT BARS IN MM;"))
(SETQ NBTOTAL(GETINT "GIVE TOTAL NUMBER OF BARS IN THE COLUMN;"))
(SETQ DIAT(GETINT "GIVE DIA OF LATERAL TIES IN MM;"))
(SETQ SPC(GETINT "GIVE SPACING OF LATERAL TIES IN MM;"))
(SETQ SCALE(GETINT "GIVE DRAWING SCALE 1: ?  ;"))
(SETQ COLUMNUM(GETSTRING "GIVE COLUMN NUMBER C- ;"))
(SETQ DIMTEXT (* 3 SCALE))
(SETQ PT1(GETPOINT "PICK FIRST EDGE OF THE COLUMN ;"))
(SETQ PT1DAS(LIST(+ (NTH 0 PT1) D)(NTH 1 PT1)))
(SETQ PT2(LIST(+ (NTH 0 PT1) (/ D 2))(NTH 1 PT1)))
(SETQ DDASL (+ 25 (/ DIAL 2)))
(SETQ PT3(LIST(+ (NTH 0 PT1) DDASL)(NTH 1 PT1)))
(SETQ PTC1(LIST(+ (NTH 0 PT3) (* 0.25 DIAL))(NTH 1 PT3)))
(COMMAND "DONUT" 0 DIAL PT3 *CANCLE*)
(SETQ PT4(LIST(+ (NTH 0 PT1) (/ D 2)) (- (NTH 1 PT1) (/ D 2))))
(COMMAND "ARRAY" PTC1 "SI" "POLAR" PT2 NBTOTAL 360 "Y" *CANCLE*)
(SETQ PT5(LIST(NTH 0 PT4)(+ (NTH 1 PT4) D)))
(SETQ PTD1(LIST(+ (NTH 0 PT1) (+ D (* 1.75 DIMTEXT)))(NTH 1 PT4)))
(SETQ PTD2(LIST(NTH 0 PT1)(+ (NTH 1 PT5) (* 0.2 D))))
(SETQ PTD3(LIST(NTH 0 PTD2)(- (NTH 1 PT4) (* 0.2 D))))
(SETQ X(- (/ D 2) 25))
(SETQ PTD4(LIST(- (NTH 0 PT2) (* X (COS 0.785)))(- (NTH 1 PT2) (* X (SIN 0.785)))))
(SETQ PTD5(LIST(+ (NTH 0 PTD2) 50)(NTH 1 PTD2)))
(SETQ PTD6(LIST(+ (NTH 0 PTD3) 50)(NTH 1 PTD3)))
(COMMAND "CIRCLE"  "2P" PT1 PT1DAS *CANCLE*)
(COMMAND "OFFSET" "25" PT1 PT2 *CANCEL*)
(COMMAND "DIM" "VERTICAL" PT4 PT5 "T" D PTD1 *CANCEL*)
(SETQ NOTE (STRCAT (ITOA NBTOTAL) "NOS." (ITOA DIAL) "MM DIA.TOR BARS"))
(COMMAND "TEXT" PTD5 (* 0.1 D) "0" NOTE *CANCLE*)
(SETQ NOTE (STRCAT "" (ITOA DIAT) "MM DIA.LATERAL RINGS @" (ITOA SPC) "MM C/C."))
(COMMAND "TEXT" PTD6 (* 0.1 D) "0" NOTE *CANCLE*)
(SETQ PTD11(LIST(NTH 0 PTD3)(- (NTH 1 PTD3) (* 2 DIMTEXT))))
(SETQ NOTE (STRCAT "%%UCOLUMN C-%%U" COLUMNUM))
(COMMAND "TEXT" PTD11 (* 0.125 D) "0" NOTE *CANCLE*)
(COMMAND "DIM" "LEADER" PT3 PTD2 PTD5 *CANCLE*)
(COMMAND "DIM" "LEADER" PTD4 PTD3 PTD6 *CANCLE*)
(COMMAND "ZOOM" "C" PT2 (* 3.5 D)) 
)
