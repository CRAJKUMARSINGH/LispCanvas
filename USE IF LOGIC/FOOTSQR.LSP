(DEFUN C:FOOTSQR()
(COMMAND "DIMSCALE" 25)
(SETQ B(GETINT "GIVE VALUE OF WIDTH OF COLUMN IN MM;"))
(SETQ D(GETINT "GIVE VALUE OF TOTAL DEPTH OF COLUMN IN MM;"))
(SETQ DIAL(GETINT "GIVE DIA OF LONGITUDINAL REINFORCEMENT BARS OF COLUMN IN MM;"))
(SETQ NBTOTAL(GETINT "GIVE TOTAL NUMBER OF BARS IN THE COLUMN;"))
(SETQ NBF(GETINT "GIVE NUMBER OF BARS ON EACH FLANGE OF COLUMN;"))
(SETQ NBS1(/ (- (FLOAT NBTOTAL) (* 2 (FLOAT NBF))) 2))
(SETQ NBS2(+ 0.5 NBS1))
(SETQ NBS(FIX NBS2))
(SETQ DIAT(GETINT "GIVE DIA OF LATERAL TIES OF COLUMN IN MM;"))
(SETQ SPC(GETINT "GIVE SPACING OF LATERAL TIES OF COLUMN IN MM;"))
(SETQ BFOOTING(GETINT "GIVE WIDTH OF COLUMN FOOTING IN MM;"))
(SETQ DEPTHEDGE(GETINT "GIVE DEPTH OF FOOTING AT EDGE IN MM;"))
(SETQ DEPTHCENTRE(GETINT "GIVE DEPTH OF FOOTING NEAR CENTRE IN MM;"))
(SETQ PCCPROJECTION(GETINT "GIVE PROJECTION OF PCC IN MM;"))
(SETQ PCCTHICKNESS(GETINT "GIVE THICKNESS OF PCC IN MM;"))
(SETQ PEDASTALPROJECTION(GETINT "GIVE PROJECTION OF PEDASTAL AT BASE OF THE COLUMN IN MM;"))
(SETQ DIAFOOTX(GETINT "GIVE DIA OF FOOTING REINFORCEMENT BARS IN X-DIRECTION IN MM;"))
(SETQ SPCX(GETINT "GIVE SPACING OF FOOTING REINFORCEMENT BARS IN X-DIRECTION IN MM;"))
(SETQ DIAFOOTY(GETINT "GIVE DIA OF FOOTING REINFORCEMENT BARS IN Y-DIRECTION IN MM;"))
(SETQ SPCY(GETINT "GIVE SPACING OF FOOTING REINFORCEMENT BARS IN Y-DIRECTION IN MM;"))
(SETQ SCALE 25)
(SETQ COLUMNUM(GETSTRING "GIVE COLUMN NUMBER C- ;"))
(SETQ DIMTEXT (* 3 SCALE))
(SETQ PT1(GETPOINT "PICK FIRST CORNER OF THE COLUMN ;"))
(SETQ PT2(LIST(+ (NTH 0 PT1) B)(NTH 1 PT1)))
(SETQ PT3(LIST(NTH 0 PT2)(+ (NTH 1 PT2) D)))
(SETQ PT4(LIST(NTH 0 PT1)(NTH 1 PT3)))
(SETQ DDASL (+ 25 (/ DIAL 2)))
(SETQ PT5(LIST(+ (NTH 0 PT1) DDASL)(+ (NTH 1 PT1) DDASL)))
(SETQ PT6(LIST(NTH 0 PT5)(- (NTH 1 PT4) DDASL)))
(SETQ PTC1(LIST(+ (NTH 0 PT5) (* 0.25 DIAL))(NTH 1 PT5)))
(SETQ SPACINGH (/ (- B (* 2 DDASL)) (- NBF 1)))
(SETQ SPACINGV (/ (- D (* 2 DDASL)) (- (+ NBS 2) 1)))
(COMMAND "DONUT" 0 DIAL PT5 NIL)
(COMMAND "ZOOM" "C" PTC1 250)
(COMMAND "ARRAY" "SI" PTC1 "RECTANGULAR" "2" NBF (- D (* 2 DDASL)) SPACINGH *CANCLE*)
(SETQ PTD1(LIST(NTH 0 PT1)(- (NTH 1 PT1) (* 1.75 DIMTEXT))))
(SETQ PTD2(LIST(- (NTH 0 PT1) (* 1.75 DIMTEXT))(NTH 1 PT1)))
(SETQ PTD3(LIST(NTH 0 PT5)(NTH 1 PT5)))
(SETQ PTD4(LIST(NTH 0 PTD3)(+ (NTH 1 PTD3) (* 0.2 D))))
(SETQ PTD5(LIST(+ (NTH 0 PTD4) B)(NTH 1 PTD4)))
(SETQ PTD6(LIST(NTH 0 PT6)(NTH 1 PT6)))
(SETQ PTD7(LIST(NTH 0 PTD6)(- (NTH 1 PTD6) (* 0.2 D))))
(SETQ PT7(LIST(NTH 0 PT5)(+ SPACINGV (NTH 1 PT5))))
(IF (= NBS 0) *CANCLE* (COMMAND "DONUT" 0 DIAL PT7 NIL))
(SETQ PTC2(LIST(+ (NTH 0 PT7) (* 0.25 DIAL))(NTH 1 PT7)))
(COMMAND "ZOOM" "C" PTC2 250)
(IF (= NBS 1) (COMMAND "ARRAY" "SI" PTC2 "RECTANGULAR" "1" 2 (- B (* 2 DDASL)) *CANCLE*) *CANCLE*)
(IF (= NBS 2) (COMMAND "ARRAY" "SI" PTC2 "RECTANGULAR" NBS 2 SPACINGV (- B (* 2 DDASL)) *CANCLE*) *CANCLE*)
(IF (= NBS 3) (COMMAND "ARRAY" "SI" PTC2 "RECTANGULAR" NBS 2 SPACINGV (- B (* 2 DDASL)) *CANCLE*) *CANCLE*)
(IF (= NBS 4) (COMMAND "ARRAY" "SI" PTC2 "RECTANGULAR" NBS 2 SPACINGV (- B (* 2 DDASL)) *CANCLE*) *CANCLE*)
(IF (= NBS 5) (COMMAND "ARRAY" "SI" PTC2 "RECTANGULAR" NBS 2 SPACINGV (- B (* 2 DDASL)) *CANCLE*) *CANCLE*)
(IF (= NBS 6) (COMMAND "ARRAY" "SI" PTC2 "RECTANGULAR" NBS 2 SPACINGV (- B (* 2 DDASL)) *CANCLE*) *CANCLE*)
(IF (= NBS 7) (COMMAND "ARRAY" "SI" PTC2 "RECTANGULAR" NBS 2 SPACINGV (- B (* 2 DDASL)) *CANCLE*) *CANCLE*)
(IF (= NBS 8) (COMMAND "ARRAY" "SI" PTC2 "RECTANGULAR" NBS 2 SPACINGV (- B (* 2 DDASL)) *CANCLE*) *CANCLE*)
(IF (= NBS 9) (COMMAND "ARRAY" "SI" PTC2 "RECTANGULAR" NBS 2 SPACINGV (- B (* 2 DDASL)) *CANCLE*) *CANCLE*)
(COMMAND "LINE" PTD3 PTD4 *CANCEL*)
(SETQ PTD8(LIST(+ (NTH 0 PTD7) B)(NTH 1 PTD7)))
(COMMAND "ZOOM" "C" PTd4 250)
(COMMAND "ARRAY" PTD4 "SI" "RECTANGULAR" "1" NBF SPACINGH *CANCLE*)

(COMMAND "LINE" PTD6 PTD7 *CANCEL*)
(COMMAND "ZOOM" "C" PTd7 250)
(COMMAND "ARRAY" PTD7 "SI" "RECTANGULAR" "1" NBF SPACINGH *CANCLE*)
(COMMAND "PLINE" PT1 PT2 PT3 PT4 "C" *CANCLE*)
(COMMAND "OFFSET" "25" PT1 PT5 *CANCEL*)
(COMMAND "DIM" "HORIZONTAL" PT1 PT2 "T" B PTD1 *CANCLE*)
(COMMAND "DIM" "VERTICAL" PT1 PT4 "T" D PTD2 *CANCEL*)
(SETQ PTD9(LIST(- (NTH 0 PT2) 25)(+ (NTH 1 PT2) (* 0.55 D))))
(SETQ PTD10(LIST(+ (NTH 0 PTD9) (+ 25 DDASL))(NTH 1 PTD9)))
(COMMAND "LINE" PTD4 PTD5 *CANCEL*)
(COMMAND "LINE" PTD7 PTD8 *CANCEL*)
(COMMAND "LINE" PTD9 PTD10 *CANCEL*)
(SETQ NOTE (STRCAT (ITOA NBF) "NOS." (ITOA DIAL) "MM DIA.TOR BARS"))
(COMMAND "TEXT" PTD5 (* 0.1 D) "0" NOTE *CANCLE*)
(SETQ NOTE (STRCAT (ITOA NBF) "NOS." (ITOA DIAL) "MM DIA.TOR BARS"))
(COMMAND "TEXT" PTD8 (* 0.1 D) "0" NOTE *CANCLE*)
(SETQ NOTE (STRCAT (ITOA DIAT) "MM DIA.LATERAL TIES @" (ITOA SPC) "MM C/C."))
(COMMAND "TEXT" PTD10 (* 0.1 D) "0" NOTE *CANCLE*)
(SETQ PTD11(LIST(NTH 0 PT1)(- (NTH 1 PT1) (* 4 DIMTEXT))))
(SETQ NOTE (STRCAT "%%UCOLUMN C-%%U" COLUMNUM))
(COMMAND "TEXT" PTD11 (* 0.125 D) "0" NOTE *CANCLE*)
(SETQ PTD12(LIST(NTH 0 PTD8)(+ (NTH 1 PTD8) (* 0.2 D))))
(SETQ NOTE (STRCAT "TOTAL NO.OF LONGITUDINAL BARS-" (ITOA (* 2 (+ NBF NBS)))))
(COMMAND "TEXT" PTD12 (* 0.1 D) "0" NOTE *CANCLE*)

;footing plan

(SETQ PTPLAN1(LIST(- (NTH 0 PT1) (/ (- bfooting b) 2))(- (NTH 1 PT1) (* BFOOTING 1.5))))
(SETQ PTPLAN2(LIST(+ (NTH 0 PTPLAN1) BFOOTING)(NTH 1 PTPLAN1)))
(SETQ PTPLAN3(LIST(NTH 0 PTPLAN2)(+ (NTH 1 PTPLAN2) BFOOTING)))
(SETQ PTPLAN4(LIST(NTH 0 PTPLAN1)(NTH 1 PTPLAN3)))
(SETQ NOX(+ (/ (- BFOOTING 80) SPCX) 1))
(SETQ NOY(+ (/ (- BFOOTING 80) SPCY) 1))
(SETQ SPCX1(/ (- BFOOTING 80) (- NOX 1)))
(SETQ SPCY1(/ (- BFOOTING 80) (- NOY 1)))
(SETQ PREINFX1(LIST(+ (NTH 0 PTPLAN1) 40)(+ (NTH 1 PTPLAN1) 40)))
(SETQ PREINFX2(LIST(- (NTH 0 PTPLAN2) 40)(NTH 1 PREINFX1)))
(SETQ PREINFY1(LIST(NTH 0 PREINFX1)(NTH 1 PREINFX1)))
(SETQ PREINFY2(LIST(NTH 0 PREINFX1)(- (NTH 1 PTPLAN4) 40)))
(COMMAND "LINE" PREINFX1 PREINFX2 *CANCEL*)
(SETQ PREINFY3(LIST(NTH 0 PREINFX1)(- (NTH 1 PREINFY2) (/ SPCX1 2))))
(COMMAND "ZOOM" "C" Preinfx2 250)
(COMMAND "ARRAY" PREINFX2 "SI" "RECTANGULAR" NOX "1" SPCX1 *CANCLE*)
(COMMAND "LINE" PREINFY1 PREINFY2 *CANCEL*)
(COMMAND "ZOOM" "C" Preinfy3 250)
(COMMAND "ARRAY" PREINFY3 "SI" "RECTANGULAR" "1" NOY SPCY1 *CANCLE*)
(COMMAND "LINE" PTPLAN1 PTPLAN2 PTPLAN3 PTPLAN4 PTPLAN1 *CANCEL*)


(SETQ PTPLAND1(LIST(NTH 0 PTPLAN1)(- (NTH 1 PTPLAN1) (* 1.75 DIMTEXT))))
(COMMAND "DIM" "HORIZONTAL" PTPLAN1 PTPLAN2 "T" BFOOTING PTPLAND1 *CANCLE*)
(SETQ PTPLAND2(LIST(- (NTH 0 PTPLAN1) (* 2.5 DIMTEXT))(NTH 1 PTPLAN1)))
(COMMAND "DIM" "VERTICAL" PTPLAN1 PTPLAN4 "T" BFOOTING PTPLAND2 *CANCEL*)
(SETQ PTPLAND3(LIST(- (NTH 0 PREINFX2) (* 3.5 SPCY1))(+ (NTH 1 PREINFX2) (* 2 SPCX1))))
(SETQ PTPLAND4(LIST(NTH 0 PTPLAND3)(+ (NTH 1 PTPLAND3) (* 1.75 DIMTEXT))))
(SETQ PTPLAND5(LIST(+ (NTH 0 PTPLAN2) (* 1.75 DIMTEXT))(NTH 1 PTPLAND4)))
(COMMAND "DIM" "LEADER" PTPLAND3 PTPLAND4 *CANCLE*)
(COMMAND "LINE" PTPLAND4 PTPLAND5 *CANCEL*)
(SETQ NOTE (STRCAT (ITOA DIAFOOTX) "MM DIA.BARS @" (ITOA SPCX) "MM C/C."))
(COMMAND "TEXT" PTPLAND5 (* 0.1 D) "0" NOTE *CANCLE*)
(SETQ PTPLAND6(LIST(+ (NTH 0 PREINFY2) (* (- NOY 3) SPCY1))(- (NTH 1 PREINFY2) (* 1.75 DIMTEXT))))
(SETQ PTPLAND7(LIST(NTH 0 PTPLAND5)(NTH 1 PTPLAND6)))
(COMMAND "DIM" "LEADER" PTPLAND6 PTPLAND7 *CANCLE*)
(COMMAND "LINE" PTPLAND6 PTPLAND7 *CANCEL*)
(SETQ NOTE (STRCAT (ITOA DIAFOOTY) "MM DIA.BARS @" (ITOA SPCY) "MM C/C."))
(COMMAND "TEXT" PTPLAND7 (* 0.1 D) "0" NOTE *CANCLE*)
(SETQ PTPLAND8(LIST(NTH 0 PTPLAN1)(- (NTH 1 PTPLAN1) (* 4 DIMTEXT))))
(SETQ NOTE (STRCAT "%%UPLAN OF FOOTING F-%%U" COLUMNUM))
(COMMAND "TEXT" PTPLAND8 (* 0.125 D) "0" NOTE *CANCLE*)

; section

(SETQ PTSECTION1(LIST(NTH 0 PTPLAN1)(- (NTH 1 PTPLAN1) (* BFOOTING 1.5))))
(SETQ PTSECTION2(LIST(+ (NTH 0 PTSECTION1) BFOOTING)(NTH 1 PTSECTION1)))
(SETQ PTSECTION3(LIST(NTH 0 PTSECTION2)(+ (NTH 1 PTSECTION2) DEPTHEDGE)))
(SETQ PTSECTION10(LIST(NTH 0 PTSECTION1)(NTH 1 PTSECTION3)))
(SETQ PTSECTION4(LIST(- (NTH 0 PTPLAN3) (- (/ (- bfooting b) 2) PEDASTALPROJECTION))(+ (NTH 1 PTSECTION1) DEPTHCENTRE)))
(SETQ PTSECTION5(LIST(- (NTH 0 PTSECTION4) PEDASTALPROJECTION)(NTH 1 PTSECTION4)))
(SETQ PTSECTION8(LIST(- (NTH 0 PTSECTION5) B)(NTH 1 PTSECTION4)))
(SETQ PTSECTION9(LIST(- (NTH 0 PTSECTION8) PEDASTALPROJECTION)(NTH 1 PTSECTION4)))
(SETQ PTSECTION6(LIST(NTH 0 PTSECTION5)(+ (NTH 1 PTSECTION5) 750)))
(SETQ PTSECTION7(LIST(NTH 0 PTSECTION8)(NTH 1 PTSECTION6)))
(SETQ PTSECTION11(LIST(- (NTH 0 PTSECTION1) PCCPROJECTION)(NTH 1 PTSECTION1)))
(COMMAND "LINE" PTSECTION1 PTSECTION10 PTSECTION9 PTSECTION8 PTSECTION7 *CANCEL*)
(COMMAND "LINE" PTSECTION2 PTSECTION3 PTSECTION4 PTSECTION5 PTSECTION6 *CANCEL*)
(SETQ PTSECTION14(LIST(+ (NTH 0 PTSECTION2) PCCPROJECTION)(NTH 1 PTSECTION1)))
(SETQ PTSECTION13(LIST(NTH 0 PTSECTION14)(- (NTH 1 PTSECTION2) PCCTHICKNESS)))
(SETQ PTSECTION12(LIST(NTH 0 PTSECTION11)(NTH 1 PTSECTION13)))
(SETQ PTSECTION16(LIST(NTH 0 PTSECTION7)(- (NTH 1 PTSECTION7) 450)))
(SETQ PTSECTION17(LIST(NTH 0 PTSECTION6)(NTH 1 PTSECTION16)))
(SETQ PTSECTION15(LIST(- (NTH 0 PTSECTION16) (/ BFOOTING 2))(NTH 1 PTSECTION16)))
(SETQ PTSECTION18(LIST(+ (NTH 0 PTSECTION17) (/ BFOOTING 2))(NTH 1 PTSECTION16)))
(SETQ PTSECTIONC(LIST(+ (NTH 0 PTSECTION12) (/ PCCTHICKNESS 2))(+ (NTH 1 PTSECTION12) (/ PCCTHICKNESS 2))))
(COMMAND "PLINE" PTSECTION11 PTSECTION12 PTSECTION13 PTSECTION14 "C" *CANCLE*)
(COMMAND "LINE" PTSECTION15 PTSECTION16 *CANCLE*)
(COMMAND "LINE" PTSECTION17 PTSECTION18 *CANCLE*)
(SETQ EXT1(/ B 4))
(SETQ EXT2(/ B 2))
(SETQ PTEH101(LIST(- (NTH 0 PTSECTION7) EXT1)(NTH 1 PTSECTION7)))
(SETQ PTEH102(LIST(NTH 0 PTSECTION7)(NTH 1 PTSECTION7)))
(SETQ PTEH103(LIST(+ (NTH 0 PTSECTION7) EXT1)(NTH 1 PTSECTION7)))
(SETQ PTEH104(LIST(+ (NTH 0 PTEH103) EXT1)(- (NTH 1 PTEH103) EXT1)))
(SETQ PTEH105(LIST(NTH 0 PTEH104)(+ (NTH 1 PTEH104) EXT2)))
(SETQ PTEH106(LIST(+ (NTH 0 PTEH105) EXT1)(NTH 1 PTEH103)))
(SETQ PTEH107(LIST(NTH 0 PTSECTION6)(NTH 1 PTSECTION6)))
(SETQ PTEH108(LIST(+ (NTH 0 PTEH107) EXT1)(NTH 1 PTEH103)))
(COMMAND "LINE" PTEH101 PTEH102 PTEH103 PTEH104 PTEH105 PTEH106 PTEH107 PTEH108 *CANCEL*)
(SETQ PSECREINFX1(LIST(NTH 0 PREINFX1)(+ (NTH 1 PTSECTION1) 40)))
(SETQ PSECREINFX2(LIST(NTH 0 PREINFX2)(NTH 1 PSECREINFX1)))
(SETQ PSECREINFY1(LIST(+ (NTH 0 PSECREINFX1) (/ DIAFOOTY 2))(+ (NTH 1 PSECREINFX1) (/ DIAFOOTY 2))))
(SETQ PSECREINFY2(LIST(NTH 0 PSECREINFY1)(+ (NTH 1 PSECREINFY1) (* 0.25 DIAFOOTY))))
(COMMAND "DONUT" 0 DIAFOOTY PSECREINFY1 NIL)
(COMMAND "ZOOM" "C" Psecreinfy2 250)
(COMMAND "ARRAY" "SI" PSECREINFY2 "RECTANGULAR" "1" NOY SPCY1 *CANCLE*)
(SETQ PSECREINFL1(LIST(NTH 0 PT5)(NTH 1 PTSECTION7)))
(SETQ PSECREINFL2(LIST(NTH 0 PT5)(+ (NTH 1 PSECREINFX1) 25)))
(SETQ PSECREINFL4(LIST(- (NTH 0 PT2) DDASL)(NTH 1 PTSECTION7)))
(SETQ PSECREINFL5(LIST(NTH 0 PSECREINFL4)(NTH 1 PSECREINFL2)))
(SETQ PSECREINFL3(LIST(- (NTH 0 PSECREINFL2) (* 0.30 BFOOTING))(NTH 1 PSECREINFL2)))
(SETQ PSECREINFL6(LIST(+ (NTH 0 PSECREINFL5) (* 0.30 BFOOTING))(NTH 1 PSECREINFL2)))
(SETQ PSECREINFTIES1(LIST(NTH 0 PSECREINFL2)(+ (NTH 1 PSECREINFL2) (/ SPC 2))))
(SETQ PSECREINFTIES2(LIST(NTH 0 PSECREINFL5)(NTH 1 PSECREINFTIES1)))
(COMMAND "LINE" PSECREINFTIES1 PSECREINFTIES2 *CANCEL*)
(SETQ PSECREINFTIESC(LIST(+ (NTH 0 PSECREINFTIES1) DDASL)(NTH 1 PSECREINFTIES1)))
(SETQ NTIES(FIX (+ (/ (- (NTH 1 PSECREINFL1) (NTH 1 PSECREINFTIES1)) SPC) 1)))
(SETQ SPC1(/ (- (NTH 1 PSECREINFL1) (NTH 1 PSECREINFTIES1)) NTIES))
(COMMAND "ZOOM" "C" Psecreinftiesc 250)
(COMMAND "ARRAY" PSECREINFTIESC "SI" "RECTANGULAR" NTIES "1" SPC1 *CANCLE*)
(COMMAND "LINE" PSECREINFL1 PSECREINFL2 *CANCEL*)
(COMMAND "ZOOM" "C" Psecreinfl2 250)
(COMMAND "ARRAY" PSECREINFL2 "SI" "RECTANGULAR" "1" NBF SPACINGH *CANCLE*)
(COMMAND "LINE" PSECREINFL2 PSECREINFL3 *CANCEL*)
(COMMAND "LINE" PSECREINFL5 PSECREINFL6 *CANCEL*)
(COMMAND "LINE" PSECREINFX1 PSECREINFX2 *CANCEL*)
(COMMAND "ZOOM" "C" Ptsection12 250)
(COMMAND "HATCH" "AR-CONC" "1" "0" "s" PTSECTION12  PTSECTION12 *cancel*  *cancel*)
(COMMAND "bHATCH" "s" PTSECTION12 "AR-CONC,N" "1" "0"  *cancel*)
(COMMAND "ZOOM" "EXTENTS")
)
