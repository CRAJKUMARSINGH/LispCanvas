(DEFUN C:BEAMRECT()
(COMMAND "DIMSCALE" 25)
(SETQ B(GETINT "GIVE VALUE OF WEB WIDTH IN MM;"))
(SETQ D(GETINT "GIVE VALUE OF TOTAL DEPTH IN MM;"))
(SETQ DIAB(GETINT "GIVE DIA OF BOTTOM BARS IN MM;"))
(SETQ NBB(GETINT "GIVE NUMBER OF BOTTOM BARS ;"))
(SETQ DIAT(GETINT "GIVE DIA OF TOP BARS IN MM;"))
(SETQ NBT(GETINT "GIVE NUMBER OF TOP BARS ;"))
(SETQ DIAS(GETINT "GIVE DIA OF SHEAR STIRRUPS BARS IN MM;"))
(SETQ SPC(GETINT "GIVE SPACING OF SHEAR STIRRUPS IN MM;"))
(SETQ BEAMNUM(GETSTRING "GIVE BEAM NUMBER ;"))
(SETQ DIMTEXT (* 3 25))
(SETQ PT1(GETPOINT "PICK FIRST CORNER OF THE BEAM ;"))
(SETQ PT2(LIST(+ (NTH 0 PT1) B)(NTH 1 PT1)))
(SETQ PT3(LIST(NTH 0 PT2)(+ (NTH 1 PT2) D)))
(SETQ PT4(LIST(NTH 0 PT1)(NTH 1 PT3)))
(SETQ DDASB (+ 25 (/ DIAB 2)))
(SETQ DDAST (+ 25 (/ DIAT 2)))
(SETQ PT5(LIST(+ (NTH 0 PT1) DDASB)(+ (NTH 1 PT1) DDASB)))
(SETQ PT6(LIST(+ (NTH 0 PT1) DDAST)(- (NTH 1 PT4) DDAST)))
(SETQ PTC1(LIST(+ (NTH 0 PT5) (* 0.25 DIAB))(NTH 1 PT5)))
(SETQ PTC2(LIST(+ (NTH 0 PT6) (* 0.25 DIAT))(NTH 1 PT6)))
(SETQ PT6(LIST(+ (NTH 0 PT1) DDAST)(- (NTH 1 PT4) DDAST)))
(SETQ SPACINGB (/ (- B (* 2 DDASB)) (- NBB 1)))
(SETQ SPACINGT (/ (- B (* 2 DDAST)) (- NBT 1)))
(COMMAND "DONUT" 0 DIAB PT5 NIL)
(COMMAND "DONUT" 0 DIAT PT6 NIL)
(SETQ PTD1(LIST(NTH 0 PT1)(- (NTH 1 PT1) (* 1.2 DIMTEXT))))
(SETQ PTD2(LIST(- (NTH 0 PT1) (* 1.2 DIMTEXT))(NTH 1 PT1)))
(SETQ PTD3(LIST(NTH 0 PT5)(NTH 1 PT5)))
(SETQ PTD4(LIST(NTH 0 PTD3)(+ (NTH 1 PTD3) (* 0.2 D))))
(SETQ PTD5(LIST(+ (NTH 0 PTD4) B)(NTH 1 PTD4)))
(SETQ PTD6(LIST(NTH 0 PT6)(NTH 1 PT6)))

(SETQ PTD7(LIST(NTH 0 PTD6)(- (NTH 1 PTD6) (* 0.2 D))))
(COMMAND "ZOOM" "C" PTC1 250)

(COMMAND "ARRAY" "SI" PTC1 "RECT" "1" NBB SPACINGB)
(COMMAND "LINE" PTD3 PTD4 *CANCEL*)

(SETQ PTD8(LIST(+ (NTH 0 PTD7) B)(NTH 1 PTD7)))
(COMMAND "ZOOM" "C" PTC2 250)
(COMMAND "ARRAY" "SI" PTC2 "RECT" "1" NBT SPACINGT)
(COMMAND "LINE" PTD6 PTD7 *CANCEL*)
(COMMAND "ZOOM" "C" PTD7 250)
(COMMAND "ARRAY" "SI" PTD7 "RECT" "1" NBT SPACINGT)
  (COMMAND "ZOOM" "C" PTD3 250)
(COMMAND "ARRAY" "SI" PTD3 "RECT" "1" NBB SPACINGB)

(COMMAND "PLINE" PT1 PT2 PT3 PT4 "C")
(COMMAND "OFFSET" "25" PT1 PT5 *CANCEL*)
(COMMAND "DIM" "HORIZONTAL" PT1 PT2 "T" B PTD1 *CANCLE*)
(COMMAND "DIM" "VERTICAL" PT1 PT4 "T" D PTD2 *CANCEL*)
(SETQ PTD9(LIST(- (NTH 0 PT2) 25)(+ (NTH 1 PT2) (* 0.50 D))))
(SETQ PTD10(LIST(+ (NTH 0 PTD9) (+ 25 DDASB))(NTH 1 PTD9)))
(COMMAND "LINE" PTD4 PTD5 *CANCEL*)
(COMMAND "LINE" PTD7 PTD8 *CANCEL*)
(COMMAND "LINE" PTD9 PTD10 *CANCEL*)
(SETQ NOTE (STRCAT (ITOA NBB) "NOS." (ITOA DIAB) "MM DIA.TOR BARS"))
(COMMAND "TEXT" PTD5 (* 0.1 D) "0" NOTE)
(SETQ NOTE (STRCAT (ITOA NBT) "NOS." (ITOA DIAT) "MM DIA.TOR BARS"))
(COMMAND "TEXT" PTD8 (* 0.1 D) "0" NOTE)
(SETQ NOTE (STRCAT (ITOA DIAS) "MM DIA.TWO LEGGED STIRRUPS @" (ITOA SPC) "MM C/C."))
(COMMAND "TEXT" PTD10 (* 0.1 D) "0" NOTE)
(SETQ PTD11(LIST(NTH 0 PT1)(- (NTH 1 PT1) (* 4 DIMTEXT))))
(SETQ NOTE (STRCAT "%%UBEAM NO.B-%%U" BEAMNUM))
(COMMAND "TEXT" PTD11 (* 0.125 D) "0" NOTE)
(COMMAND "ZOOM" "C" PTD10 250) 
)
